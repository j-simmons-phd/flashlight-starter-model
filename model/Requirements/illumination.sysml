requirement illumination {
    // the following is a simple text based requirement
    requirement fieldOfView {
        doc /* The flashlight field of view shall be 0 - 20 degrees. */
    }
    requirement lightPower {
        doc /* The light power shall be a minimum of TBD lumens */
    }
}
