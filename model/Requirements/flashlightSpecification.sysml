requirement flashlightSpecification {
    requirement userInterface;
    m4_include(Requirements/illumination.sysml)
    m4_include(Requirements/physical.sysml)
    requirement reliability;
    requirement cost;
}
